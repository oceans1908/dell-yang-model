module sonic-bgp-common {
    namespace "http://github.com/Azure/sonic-bgp-common";
    prefix sbc;
    yang-version 1.1;

    import ietf-inet-types {
        prefix inet;
    }

    import sonic-port {
        prefix prt;
    }

    import sonic-portchannel {
        prefix spc;
    }

    import sonic-vlan {
        prefix svlan;
    }

    import sonic-loopback {
        prefix lo;
    }

    import sonic-routing-policy-sets {
        prefix srpolsets;
    }

    import sonic-route-map {
        prefix srmap;
    }

    import sonic-common {
        prefix cmn;
    }

    import ietf-yang-types {
        prefix ietf-yang;
    }

    import sonic-interface {
        prefix sintf;
    }

    import sonic-extension {
        prefix sonic-ext;
    }

    organization
        "SONiC";

    contact
        "SONiC";

    description
        "SONIC BGP common YANG attributes for Neighbors and Peer group";

    revision 2024-12-16 {
        description
            "Added yang max_prefix_discard_extra and neccessary constraints.";
    }

    revision 2022-12-16 {
        description
            "Added yang constraints for ebgp_multihop_ttl, ttl_security_hops, max_prefix_warning_only, max_prefix_restart_interval.";
    }

    revision 2021-02-01 {
        description
            "Added CVL check to compare strict_capability_match and override_capability.";
    }

    revision 2021-01-08 {
        description
            "Added support for routed vlan-sub-interface.";
    }

    revision 2020-07-26 {
        description
            "Change for sonic-loopback.yang.";
    }
    revision 2019-11-04 {
        description
            "Initial revision.";
    }

    typedef bgp_peer_type {
        type enumeration {
            enum internal {
                description "Internal peer";
            }
            enum external {
                description "External peer";
            }
        }
    }

    typedef bgp_tx_add_paths_type {
      type enumeration {
          enum tx_all_paths {
              description
                  "Send multiple path advertisements for an NLRI from 
                  the neighbor or group";
          }
          enum tx_best_path_per_as {
              description
                  "Send only best path per AS advertisements for an NLRI from 
                  the neighbor or group";
          }
          enum tx_all_backup_paths {
              description
                  "Select best and backup paths along with ECMP paths as
                  candidated to be advertised as additional paths";
          }
          enum tx_best_and_backup_paths {
              description
                  "Select best and back path to be advertised as additional paths";
          }
      }
      description
          "Type to describe the add paths advertisement method.";
    }

    typedef bgp_community_type {
        type enumeration {
            enum standard {
                description "Standard communities";
            }

            enum extended {
                description "Extended communities";
            }

            enum both {
                description "Both standard and extended communities";
            }

            enum large {
                description "Large communities";
            }

            enum all {
                description "Standard, Extended and Large communities";
            }

            enum none {
                description "No community attribute";
            }
        }
        description
            "type describing variations of community attributes";
    }

    typedef sonic_bgp_direction {
        type enumeration {
            enum in {
                description
                    "Refers to information received from the BGP peer";
            }
            enum out {
                description
                    "Refers to information advertised to the BGP peer";
            }
        }
        description
            "Type to describe the direction";
    }

    typedef sonic_bgp_orf {
        type enumeration {
            enum send {
                description
                    "Capability to receive the outbound route filtering from this neighbor";
            }
            enum receive {
                description
                    "Capability to send the outbound route filtering to this neighbor";
            }
            enum both {
                description
                    "Capability to send and receive the outbound route filtering to/from this neighbor";
            }
        }
        description
            "Type to describe the BGP ORF(Outbound route filtering) capability";
    }

    grouping sonic-bgp-cmn {

        leaf local_asn {
            type uint32 {
                range "1..4294967295";
            }
            description "Local AS number";
            sonic-ext:custom-validation ValidateBgpLocalAsNum;
        }

        leaf name {
            type string;
            description "Peer description";
        }

        leaf asn {
            must "not (current()/../peer_type)" {
                error-message "Can't specify ASN as BGP neighbor as peer type is set";
            }
            type uint32 {
                range "1..4294967295";
            }
            description "Peer AS number";
            sonic-ext:custom-validation ValidateBgpPeerGrpRemoteAsNum;
        }

        leaf peer_type {
            must "not (current()/../asn)" {
                error-message "Can't specify peer type as BGP neighbor as ASN is set";
            }
            type bgp_peer_type;
            sonic-ext:custom-validation ValidateBgpPeerGrpRemoteAsNum;
        }

        leaf ebgp_multihop {
            type boolean;
            description "EBGP Multihop enabled";
        }

        leaf ebgp_multihop_ttl {
            must "not (current()/../ttl_security_hops)" {
                error-message "ebgp_multihop_ttl is not supported with ttl_security_hops";
            }
            type uint8 {
                range "1..255";
            }
            description "EBGP Multihop TTL";
        }

        leaf auth_password {
            sonic-ext:custom-validation ValidateEncryptedKey;
            type string;
            description "Authuntiation password";
        }

        leaf keepalive {
            type uint16;
            description "Keepalive interval";
        }

        leaf holdtime {
            type uint16;
            description "Hold time";
        }

        leaf conn_retry {
            type uint16 {
                range "1..65535";
            }
            description "Connection retry time";
        }

        leaf min_adv_interval {
            type uint16 {
                range "0..600";
            }
            description "minium advertisement interval";
        }

        leaf local_addr {
            type union {
                type inet:ip-address;
                type leafref {
                    path "/prt:sonic-port/prt:PORT/prt:PORT_LIST/prt:ifname";
                }
                type leafref {
                    path "/spc:sonic-portchannel/spc:PORTCHANNEL/spc:PORTCHANNEL_LIST/spc:name";
                }
                type leafref {
                    path "/sintf:sonic-interface/sintf:VLAN_SUB_INTERFACE/sintf:VLAN_SUB_INTERFACE_LIST/sintf:id";
                }
                type leafref {
                    path "/svlan:sonic-vlan/svlan:VLAN/svlan:VLAN_LIST/svlan:name";
                }
                type leafref {
                    path "/lo:sonic-loopback/lo:LOOPBACK/lo:LOOPBACK_LIST/lo:name";
                }
            }
            description "Local source address or interface name to use for connection.";
        }

        leaf passive_mode {
            type boolean;
            description "Passive mode";
        }

        leaf capability_ext_nexthop {
            type boolean;
            description "Advertise extended nexthop capability";
        }

        leaf disable_ebgp_connected_route_check {
            type boolean;
            description "Connected checked disabled";
            sonic-ext:custom-validation ValidateDisableConnectedCheck;
        }

        leaf enforce_first_as {
            type boolean;
            description "Enforce first AS for EBGP";
        }

        leaf solo_peer {
            type boolean;
            description "Part of own update group";
        }

        leaf ttl_security_hops {
            must "not (current()/../ebgp_multihop_ttl)" {
                error-message "ttl_security_hops is not supported with ebgp_multihop_ttl";
            }
            type uint8 {
                range 1..254;
            }
            sonic-ext:custom-validation ValidateConnectedInterfaceCheck;
            description "TTL";
        }

        leaf bfd {
            type boolean;
            description "BFD status";
        }

        leaf bfd_check_ctrl_plane_failure {
            type boolean;
            description "Link dataplane status with BGP control plane";
        }

        leaf bfd_profile {
            type string {
                length "1..64";
            }
            description "BFD Profile name format";
        }

        leaf capability_dynamic {
            type boolean;
            description "Advertise dynamic capability";
        }

        leaf dont_negotiate_capability {
            type boolean;
            description "Do not perform capability negotiation";
        }

        leaf enforce_multihop {
            type boolean;
            description "Enforce EBGP neighbors perform multihop";
        }

        leaf override_capability {
            type boolean;
            description "Override capability negotiation result";
        }

        leaf peer_port {
            type uint16;
            description "Peer port number";
        }

        leaf shutdown_message {
            type string {
                length "1..127";
            }
            description "Message on peer/Neighbor shutdown";
        }

        leaf strict_capability_match {
            type boolean;
            sonic-ext:custom-validation ValidateStrictAndOverRideCapability;
            description "Strict capability negotiation match";
        }

        leaf admin_status {
            type boolean;
            description "To enable BGP peer";
        }

        leaf local_as_no_prepend {
            type boolean;
            description "Do not prepend local-as to updates from ebgp peers";
        }

        leaf local_as_replace_as {
            type boolean;
            description "Do not prepend local-as to updates from ibgp peers";
        }

        leaf extended_link_bandwidth {
            type boolean;
            description "Use extended link bandwidth community for the peers";
        }
	}


    grouping sonic-bgp-cmn-af {

        leaf afi_safi {
            type string;
            description "Address family";
        }

        leaf admin_status {
            type boolean;
            description "Enabled status";
        }

        leaf send_default_route {
            type boolean;
            description "Send default route";
        }

        leaf default_rmap {
            type leafref {
                path "/srmap:sonic-route-map/srmap:ROUTE_MAP_SET/srmap:ROUTE_MAP_SET_LIST/srmap:name";
            }
            description "Default route map to originate";
        }

        leaf max_prefix_limit {
            type uint32;
            description "Maximum prefix limit";
        }

        leaf max_prefix_warning_only {
            must "current()='false' or not (current()/../max_prefix_restart_interval)" {
               error-message "prevent-teardown is not supported with restart-timer";
            }
            must "current()='false' or not (current()/../max_prefix_discard_extra = 'true')" {
               error-message "prevent-teardown is not supported with discard-extra";
			}
            type boolean;
            description "On maximum prefix limit, warn only";
        }

        leaf max_prefix_warning_threshold {
            type uint8 {
                range "1..100";
            }
            description "Maximum prefix limit threshold for warning";
        }

        leaf max_prefix_restart_interval {
            must "current()/../max_prefix_warning_only='false' or not (current()/../max_prefix_warning_only)" {
               error-message "restart-timer is not supported with prevent-teardown";
            }
            must "current()/../max_prefix_discard_extra='false' or not (current()/../max_prefix_discard_extra)" {
               error-message "restart-timer is not supported with discard-extra";
			}
            type uint16 {
                range "1..65535";
            }
            description "Interval after which connection will get re-established";
        }

        leaf max_prefix_discard_extra {
            must "current()='false' or not (current()/../max_prefix_restart_interval)" {
               error-message "discard-extra is not supported with restart-timer";
            }
            must "current()='false' or not (current()/../max_prefix_warning_only = 'true')" {
               error-message "discard-extra is not supported with prevent-teardown";
            }
            type boolean;
            description "On maximum prefix limit, discard extra prefix";
        }

        leaf-list route_map_in {
            type leafref {
                path "/srmap:sonic-route-map/srmap:ROUTE_MAP_SET/srmap:ROUTE_MAP_SET_LIST/srmap:name";
            }
            must "(/cmn:operation/cmn:operation = 'DELETE') or (count(current()) = 1)" {
                error-app-tag "max-allowed-route-map-reached";
                error-message "Only one route-map can be associated";
            }
        }

        leaf-list route_map_out {
            type leafref {
                path "/srmap:sonic-route-map/srmap:ROUTE_MAP_SET/srmap:ROUTE_MAP_SET_LIST/srmap:name";
            }
            must "(/cmn:operation/cmn:operation = 'DELETE') or (count(current()) = 1)" {
                error-app-tag "max-allowed-route-map-reached";
                error-message "Only one route-map can be associated";
            }
        }

        leaf soft_reconfiguration_in {
            type boolean;
            description "Inbound soft reconfiguration";
        }

        leaf unsuppress_map_name {
            type leafref {
                path "/srmap:sonic-route-map/srmap:ROUTE_MAP_SET/srmap:ROUTE_MAP_SET_LIST/srmap:name";
            }
            description "Route map";
        }

        leaf rrclient {
            type boolean;
            description "Route reflector client";
        }

        leaf weight {
            type uint16 {
                range 0..65535;
            }
        }

        leaf as_override {
            type boolean;
        }

        leaf send_community {
            must "current()/../afi_safi = 'ipv4_unicast' or current()/../afi_safi = 'ipv6_unicast'" {
                error-message "Send community is supported only for ipv4 and ipv6 unicast address families!";
            }
            type bgp_community_type;
        }

        leaf tx_add_paths {
            type bgp_tx_add_paths_type;
            description "Advertise all paths or best path per AS using add path";
        }

        leaf unchanged_as_path {
            type boolean;
            description "AS path attribute unchanged";
        }

        leaf unchanged_med{
            type boolean;
            description "MED attribute unchanged";
        }

        leaf unchanged_nexthop {
            type boolean;
            description "nexthop attribute unchanged";
        }
        
        leaf filter_list_in {
            type leafref {
                path "/srpolsets:sonic-routing-policy-sets/srpolsets:AS_PATH_SET/srpolsets:AS_PATH_SET_LIST/srpolsets:name";
            }
            description "Filter list name";
        }

        leaf filter_list_out {
            type leafref {
                path "/srpolsets:sonic-routing-policy-sets/srpolsets:AS_PATH_SET/srpolsets:AS_PATH_SET_LIST/srpolsets:name";
            }
            description "Filter list name";
        }
        
        leaf nhself {
            type boolean;
            description "Nexthop is self, no nexthop calculation";
        }

        leaf nexthop_self_force {
            type boolean;
            description "Force nexthop to be self for reflected routes";
        }
        
        leaf prefix_list_in {
            type leafref {
                path "/srpolsets:sonic-routing-policy-sets/srpolsets:PREFIX_SET/srpolsets:PREFIX_SET_LIST/srpolsets:name";
            }
            description "Prefix list name";
        }

        leaf prefix_list_out {
            type leafref {
                path "/srpolsets:sonic-routing-policy-sets/srpolsets:PREFIX_SET/srpolsets:PREFIX_SET_LIST/srpolsets:name";
            }
            description "Prefix list name";
        }
        
        leaf remove_private_as_enabled {
            type boolean;
            description "Remove private ASN's in outbound updates";
        }

        leaf replace_private_as {
            type boolean;
            description "Replace private ASN's with our ASN in outbound updates";
        }

        leaf remove_private_as_all {
            type boolean;
            description "Remove all ASN's in outbound updates";
        }

        leaf allow_as_in {
            type boolean;
            description "Allow own ASN in AS path";
        }

        leaf allow_as_count {
            type uint8;
            description "Number of occurances of ASN";
        }

        leaf allow_as_origin {
            type boolean;
            description "Allow own AS in AS path, if route originated in own AS";
        }

        leaf cap_orf {
            type sonic_bgp_orf;
            description "ORF(Outbound Route Filtering) capability";
        }

        leaf route_server_client {
            type boolean;
            description "Route server client";
        }

        leaf fabric_external {
            must "current()/../afi_safi = 'l2vpn_evpn'" {error-message "Fabric external is supported only for l2vpn address family!"; }
            type boolean;
            description "Allow next-hop rewrite while advertising the route";
        }
    }

    grouping sonic-bgp-evpn-vni-common {

        leaf advertise-default-gw {
            type boolean;
        }

        leaf advertise-svi-ip {
            type boolean;
        }

        leaf route-distinguisher {
            type string;
        }

        leaf-list import-rts {
            type string;
        }

        leaf-list export-rts {
            type string;
        }

        leaf advertise-pip {
            type boolean;
            default true;
            description
               "Enable advertise PIP";
        }

        leaf advertise-pip-ip {
            type inet:ipv4-address;
            description
               "PIP IPv4 address";
        }

        leaf advertise-pip-peer-ip {
            must "current()/../vrf_name = 'default'" {
                error-message "Advertise peer ip is supported only on default VRF!";
            }
            type inet:ipv4-address;
            description
               "PIP peer IPv4 address";
        }
    }

    grouping sonic-bgp-af-evpn-global {

        uses sonic-bgp-evpn-vni-common;

        leaf advertise-all-vni {
            must "current()/../vrf_name = 'default'" { 
                error-message "Advertise all VNI is only supported on default VRF!"; 
            }
            type boolean;
        }     

        leaf default-originate-ipv4 {
            type boolean;
        }

        leaf default-originate-ipv6 {
            type boolean;
        } 

        leaf autort {
            type string;
        }

        /*leaf flooding {
            type string;
        }*/

        leaf dad-enabled {
            must "((../advertise-all-vni='true') or (current()='true'))" {
                error-message "dup-addr-detection cannot be false under non-EVPN VRF";
            }
            type boolean;
            default true;
        } 

        leaf dad-max-moves {
            type uint32;
        }

        leaf dad-time {
            type uint32;
        }

        leaf dad-freeze {
            type string;
        } 

        leaf disable-ead-evi-rx {
            must "current()/../vrf_name = 'default'" { 
                error-message "disable-ead-evi-rx is only supported on default VRF!"; 
            }
            type boolean;
        }

        leaf disable-ead-evi-tx {
            must "current()/../vrf_name = 'default'" { 
                error-message "disable-ead-evi-tx is only supported on default VRF!"; 
            }
            type boolean;
        }

    }

}
