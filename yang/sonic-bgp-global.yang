module sonic-bgp-global {
    namespace "http://github.com/Azure/sonic-bgp-global";
    prefix sbgpg;
    yang-version 1.1;

    import sonic-vrf {
        prefix svrf;
    }

    import ietf-inet-types {
        prefix inet;
    }

    import sonic-bgp-common {
        prefix sbc;
    }

    import sonic-route-map {
        prefix srmap;
    }

    import sonic-extension {
        prefix sonic-ext;
    }

    import sonic-common {
        prefix cmn;
    }

    organization
        "SONiC";

    contact
        "SONiC";

    description
        "SONIC BGP Global YANG";

    revision 2022-02-09 {
        description
            "Updated write_quanta range";
    }

    revision 2022-12-16 {
        description
            "Added CVL check for BGP Vrf, BGP Vrf As Number and made local_asn as mandatory field.";
    }

    revision 2020-12-10 {
        description
            "Added CVL validation condition to compare max_delay and establish_wait values.";
    }

    revision 2019-11-20 {
        description
            "Added BGP fields for extensive features.";
    }

    revision 2019-09-15 {
        description
            "Initial revision.";
    }

    typedef as_notation_type {
      type enumeration {
        enum asplain {
          description
            "AS numbers using decimal integer notation.";
        }
        enum asdot {
          description
            "AS number values less than 65536 using asplain notation and representing
             AS number values equal to or greater than 65536 using asdot+ notation.";
        }
        enum asdot+ {
          description
            "AS numbers using a notation of two integer values joined by a period character:
             <high order 16-bit value in decimal>.<low order 16-bit value in decimal>.";
        }
      }
    }

    typedef compare_linkbw_type {
      type enumeration {
        enum default_wt {
          description
            "Assign a low default weight (value 1) to paths not having link bandwidth";
        }
        enum ignore_lb {
          description
            "Ignore link bandwidth (i.e.,  do regular ECMP,  not weighted)";
        }
        enum skip_missing {
          description
            "Ignore paths without link bandwidth for ECMP (if other paths have it)";
        }
      }
    }

    container sonic-bgp-global {
        container BGP_GLOBALS {
            list BGP_GLOBALS_LIST {
                key "vrf_name";

                leaf vrf_name {
                    type union {
                        type string {
                            pattern "default";
                        }
                        type leafref {
                            path "/svrf:sonic-vrf/svrf:VRF/svrf:VRF_LIST/svrf:vrf_name";
                        }
                    }
                    sonic-ext:custom-validation ValidateBgpVrfConfig;
                    sonic-ext:custom-validation ValidateBgpAsNum;
                }

                leaf router_id {
                    type inet:ipv4-address;
                }

                leaf local_asn {
                    mandatory true;
                    type uint32 {
                        range "1..4294967295";
                    }
                }

                leaf always_compare_med {
                    type boolean;
                }

                leaf load_balance_mp_relax {
                    type boolean;
                }

                leaf graceful_restart_enable {
                    type boolean;
                }

                leaf gr_preserve_fw_state {
                    type boolean;
                    description
                        "Set F-bit indication that FIB is preserved while doing Graceful Restart.";
                }

                leaf gr_restart_time {
                    type uint16 {
                        range "1..3600";
                    }
                }

                leaf gr_stale_routes_time {
                    type uint16 {
                        range "1..3600";
                    }
                }

                leaf external_compare_router_id {
                    type boolean;
                }

                leaf ignore_as_path_length {
                    type boolean;
                }
                
                leaf compare_linkbw {
                    type compare_linkbw_type;
                }

                leaf log_nbr_state_changes {
                    type boolean;
                }

                leaf rr_cluster_id {
                    type string;
                }

                leaf rr_allow_out_policy {
                    type boolean;
                }

                leaf disable_ebgp_connected_rt_check {
                    type boolean;
                }

                leaf fast_external_failover {
                    type boolean;
                }

                leaf network_import_check {
                    type boolean;
                }

                leaf graceful_shutdown {
                    type boolean;
                }

                leaf rr_clnt_to_clnt_reflection {
                    type boolean;
                    description
                        "Enable client to client route reflection.";
                }

                leaf max_dynamic_neighbors {
                    type uint16 {
                        range 1..5000;
                    }
                    description
                        "Maximum number of BGP dynamic neighbors that can be created.";
                }

                leaf read_quanta {
                    type uint8 {
                        range 1..10;
                    }
                    description
                        "This indicates how many packets to read from peer socket per I/O cycle";
                }

                leaf write_quanta {
                    type uint8 {
                        range 1..64;
                    }
                    description
                        "This indicates how many packets to write to peer socket per run";
                }

                leaf coalesce_time {
                    type uint32;
                    description
                        "Subgroup coalesce timer value in milli-sec";
                }

                leaf route_map_process_delay {
                    type uint16 {
                        range 0..600;
                    }
                    description
                        "0 disables the timer, no route updates happen when route-maps change";
                }

                leaf deterministic_med {
                    type boolean;
                    description
                        "Pick the best-MED path among paths advertised from the neighboring AS.";
                }

                leaf med_confed {
                    type boolean;
                    description
                        "Compare MED among confederation paths when set to true.";
                }

                leaf med_missing_as_worst {
                    type boolean;
                    description
                        "Treat missing MED as the least preferred one when set to true.";
                }

                leaf compare_confed_as_path {
                    type boolean;
                    description
                        "Compare path lengths including confederation sets & sequences in selecting a route";
                }

                leaf as_path_mp_as_set {
                    type boolean;
                    description
                        "Generate an AS_SET.";
                }

                leaf default_ipv4_unicast {
                    type boolean;
                    description
                        "Activate ipv4-unicast for a peer by default";
                }

                leaf default_local_preference {
                    type uint32;
                    description
                        "Configure default local preference value.";
                }

                leaf default_show_hostname {
                    type boolean;
                    description
                        "Show hostname in BGP dumps.";
                }

                leaf default_shutdown {
                    type boolean;
                    description
                        "Apply administrative shutdown to newly configured peers.";
                }

                leaf default_subgroup_pkt_queue_max {
                    type uint8 {
                        range 20..100;
                    }
                    description
                        "Configure subgroup packet queue max.";
                }

                leaf max_med_time {
                    type uint32{
                        range 5..86400;
                    }
                    description
                        "Time (seconds) period for max-med";
                }

                leaf max_med_val {
                    type uint32;
                    description
                        "Max MED value to be used";
                }

                leaf max_med_admin {
                    type boolean;
                    description
                        "Enable Max MED admin status.";
                }

                leaf max_med_admin_val {
                    type uint32;
                    description
                        "Administrative Max MED value to be used";
                }


                leaf max_delay {
                    type uint16 {
                        range 0..3600;
                    }
                    description
                        "Maximum delay for best path calculation.";
                }

                leaf establish_wait {
                    type uint16 {
                        range 0..3600;
                    }
                    sonic-ext:custom-validation ValidateMaxDelayAndEstWait;
                    description
                        "Maximum delay for updates.";
                }

                leaf confed_id {
                    type uint32 {
                        range "1..4294967295";
                    }
                    description
                        "Set routing domain confederation AS.";
                }

                leaf-list confed_peers {
                    type uint32 {
                        range "1..4294967295";
                    }
                    description
                        "Peer ASs in BGP confederation";
                }

                leaf keepalive {
                    type uint16;
                    description "Keepalive interval";
                }

                leaf holdtime {
                    type uint16;
                    description "Hold time";
                }

                leaf ebgp_requires_policy {
                    type boolean;
                    description "Require in and out policy for eBGP peers (RFC8212)";
                    default false;
                }

                leaf as_notation {
                    type as_notation_type;
                    description "AS-notation for AS numbers.";
                }
            }
        }

        container BGP_GLOBALS_AF {
            list BGP_GLOBALS_AF_LIST {
                key "vrf_name afi_safi";

                leaf vrf_name {
                    type leafref {
                        path "../../../BGP_GLOBALS/BGP_GLOBALS_LIST/vrf_name";
                    }
                }

                leaf afi_safi {
                    type string;
                }

                leaf max_ebgp_paths {
                    type uint16 {
                        range "1..256";
                    }
                    sonic-ext:custom-validation ValidateMaxEbgpPathCheck;
                }

                leaf max_ibgp_paths {
                    type uint16 {
                        range "1..256";
                    }
                    sonic-ext:custom-validation ValidateMaxIbgpPathCheck;
                }

                leaf-list import_vrf {
                    type union {
                        type string {
                            pattern "default";
                        }
                        type leafref {
                            path "../../../BGP_GLOBALS/BGP_GLOBALS_LIST/vrf_name";
                        }
                    }
                    sonic-ext:custom-validation ValidateImportVrf;
                }

                leaf import_vrf_route_map {
                    type leafref {
                        path "/srmap:sonic-route-map/srmap:ROUTE_MAP_SET/srmap:ROUTE_MAP_SET_LIST/srmap:name";
                    }
                    sonic-ext:custom-validation ValidateDefaultVrfBGP;
                }

                leaf route_download_filter {
                    type leafref {
                        path "/srmap:sonic-route-map/srmap:ROUTE_MAP_SET/srmap:ROUTE_MAP_SET_LIST/srmap:name";
                    }
                }

                leaf ebgp_route_distance {
                    type uint8 {
                        range "1..255";
                    }
                }

                leaf ibgp_route_distance {
                    type uint8 {
                        range "1..255";
                    }
                }

                leaf local_route_distance {
                    type uint8 {
                        range "1..255";
                    }
                }

                leaf ibgp_equal_cluster_length {
                    type boolean;
                    description
                        "Match the cluster length.";
                }
                
                leaf route_flap_dampen {
                    must "current()/../afi_safi = 'ipv4_unicast'" { error-message "Route flap dampening is supported only for IPv4 address family!"; }
                    type boolean;
                }

                leaf route_flap_dampen_half_life {
                    must "current()/../afi_safi = 'ipv4_unicast'" { error-message "Route flap dampening is supported only for IPv4 address family!"; }
                    type uint8 {
                        range "1..45";
                    }
                }

                leaf route_flap_dampen_reuse_threshold {
                    must "current()/../afi_safi = 'ipv4_unicast'" { error-message "Route flap dampening is supported only for IPv4 address family!"; }
                    type uint16 {
                        range "1..20000";
                    }
                }

                leaf route_flap_dampen_suppress_threshold {
                    must "current()/../afi_safi = 'ipv4_unicast'" { error-message "Route flap dampening is supported only for IPv4 address family!"; }
                    type uint16 {
                        range "1..20000";
                    }
                }

                leaf route_flap_dampen_max_suppress {
                    must "current()/../afi_safi = 'ipv4_unicast'" { error-message "Route flap dampening is supported only for IPv4 address family!"; }
                    type uint8 {
                        range "1..255";
                    }
                }
                leaf backup_paths_compute {
                    must "(current()/../afi_safi = 'ipv4_unicast') or (current()/../afi_safi = 'ipv6_unicast')" {
                        error-message "backup-path-compute is supported only for IPv4/IPv6 address family!";
                    }
                    type boolean;
                }
                leaf backup_paths_install {
                    must "(current()/../afi_safi = 'ipv4_unicast') or (current()/../afi_safi = 'ipv6_unicast')" {
                        error-message "backup-path-compute-install is supported only for IPv4/IPv6 address family!";
                    }
                    type boolean;
                    sonic-ext:custom-validation ValidatePlatformToInstallBackupPath;
                }
                uses sbc:sonic-bgp-af-evpn-global;
            }
        }

        container BGP_GLOBALS_AF_AGGREGATE_ADDR {
            list BGP_GLOBALS_AF_AGGREGATE_ADDR_LIST {
                key "vrf_name afi_safi ip_prefix";

                leaf vrf_name {
                    type leafref {
                        path "../../../BGP_GLOBALS/BGP_GLOBALS_LIST/vrf_name";
                    }
                }

                leaf afi_safi {
                    type string;
                }

                leaf ip_prefix {
                    type inet:ip-prefix;
                }

                leaf as_set {
                    type boolean;
                }

                leaf summary_only {
                    type boolean;
                }

                leaf policy {
                    type leafref {
                        path "/srmap:sonic-route-map/srmap:ROUTE_MAP_SET/srmap:ROUTE_MAP_SET_LIST/srmap:name";
                    }
                }
            }
        }

        container BGP_GLOBALS_AF_NETWORK {
            list BGP_GLOBALS_AF_NETWORK_LIST {
                key "vrf_name afi_safi ip_prefix";

                leaf vrf_name {
                    type leafref {
                        path "../../../BGP_GLOBALS/BGP_GLOBALS_LIST/vrf_name";
                    }
                }

                leaf afi_safi {
                    type string;
                }

                leaf ip_prefix {
                    type inet:ip-prefix;
                }

                leaf policy {
                    type leafref {
                        path "/srmap:sonic-route-map/srmap:ROUTE_MAP_SET/srmap:ROUTE_MAP_SET_LIST/srmap:name";
                    }
                }

                leaf backdoor {
                    type boolean;
                    sonic-ext:custom-validation ValidateAfisafiForBackdoor;
                }
            }
        }

        container BGP_GLOBALS_EVPN_RT {
            list BGP_GLOBALS_EVPN_RT_LIST {
                key "vrf afi-safi-name route-target";

                leaf vrf {
                    type string;
                }

                leaf afi-safi-name {
                    type string;
                }

                leaf route-target {
                    type string;
                }

                leaf route-target-type {
                    type string;
                }
            }
        }

        container BGP_GLOBALS_EVPN_VNI {
            list BGP_GLOBALS_EVPN_VNI_LIST {
                key "vrf afi-safi-name vni-number";

                leaf vrf {
                    type leafref {
                        path "../../../BGP_GLOBALS_AF/BGP_GLOBALS_AF_LIST/vrf_name";
                    }                
                }

                leaf afi-safi-name {
                    type string;
                }

                leaf vni-number {
                      must "(/cmn:operation/cmn:operation = 'DELETE') or ((translate(current()/../afi-safi-name, 'ABCDEFGHIJKLMNOPQRSTUVWXYZ', 'abcdefghijklmnopqrstuvwxyz') = 'l2vpn_evpn') and  (../../../BGP_GLOBALS_AF/BGP_GLOBALS_AF_LIST[vrf_name=current()/../vrf][afi_safi='l2vpn_evpn']/advertise-all-vni = 'true'))" {
                        error-message "This command is only supported under EVPN VRF";
                    }
                    type uint32;
                }

                uses sbc:sonic-bgp-evpn-vni-common;
            }
        }

        container BGP_GLOBALS_EVPN_VNI_RT {
            list BGP_GLOBALS_EVPN_VNI_RT_LIST {
                key "vrf afi-safi-name vni-number route-target";

                leaf vrf {
                    type string;
                }

                leaf afi-safi-name {
                    type string;
                }

                leaf vni-number {
                    type uint32;
                }

                leaf route-target {
                    type string;
                }

                leaf route-target-type {
                    type string;
                }
            }
        }
        container BGP_GLOBALS_ROUTE_ADVERTISE {
            list BGP_GLOBALS_ROUTE_ADVERTISE_LIST {
                key "vrf dst-afi-safi-name src-afi-safi-name";

                leaf vrf {
                    type leafref {
                        path "../../../BGP_GLOBALS/BGP_GLOBALS_LIST/vrf_name";
                    }
                }

                leaf dst-afi-safi-name {
                    type string;
                }

                leaf src-afi-safi-name {
                    type string;
                }

                leaf-list policy{
                    type leafref {
                        path "/srmap:sonic-route-map/srmap:ROUTE_MAP_SET/srmap:ROUTE_MAP_SET_LIST/srmap:name";
                    }
                    must "(/cmn:operation/cmn:operation = 'DELETE') or (count(current()) = 1)" {
                        error-app-tag "max-allowed-route-map-reached";
                        error-message "Only one route-map can be associated";
                    }
                }
            }
        }
    }
}
