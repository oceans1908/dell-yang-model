module openconfig-dcbx-rpc-annot {
    yang-version "1";

    namespace "http://openconfig.net/yang/dcbx-rpc-annot";
    prefix "oc-dcbx-rpc-annot";

    import sonic-extensions { prefix sonic-ext; }
    import openconfig-dcbx-rpc { prefix oc-dcbx-rpc; }

    // meta
    organization
        "OCP SONiC Subproject";

    contact
        "OCP SONiC Subproject Working Group
        https://github.com/Azure/SONiC";

    description
        "SONIC dcbx";

	revision "2024-07-10" {
		description
		  "Initial revision";
		reference "0.1.0";
	}

    deviation /oc-dcbx-rpc:clear-dcbx-statistics {
        deviate add {
            sonic-ext:rpc-callback "rpc_clear_dcbx_stats";
            sonic-ext:user-role-priv "rpc:netadmin";
        }
    }
}
