module sonic-transceiver {
    namespace "http://github.com/Azure/sonic-transceiver";
    prefix sxcvrdiag;

    import sonic-port {
        prefix prt;
    }

    import sonic-extension {
        prefix sonic-ext;
    }

    organization
        "SONiC";

    contact
        "SONiC";

    description
        "SONiC Transceiver Information";

    revision 2020-06-10 {
        description
            "Initial revision.";
    }

    container sonic-transceiver {

        container TRANSCEIVER_DIAG {
            sonic-ext:db-name "CONFIG_DB";
            list TRANSCEIVER_DIAG_LIST {
                key "ifname";

                leaf ifname {
                    type leafref {
                        path "/prt:sonic-port/prt:PORT/prt:PORT_LIST/prt:name";
                    }
                }
                leaf lb_media_input_enabled {
                    type string;
                    description "Line/Media side input loopback enablement";
                }
                leaf lb_media_output_enabled {
                    type string;
                    description "Line/Media side output loopback enablement";
                }
                leaf lb_host_input_enabled {
                    type string;
                    description "System/Host side input loopback enablement";
                }
                leaf lb_host_output_enabled {
                    type string;
                    description "System/Host side output loopback enablement";
                }
                leaf prbs_chk_host_enabled {
                    type string;
                    description "System/Host side PRBS pattern checking enablement";
                }
                leaf prbs_chk_media_enabled {
                    type string;
                    description "Media/Line side PRBS pattern checking enablement";
                }
                leaf prbs_gen_host_enabled {
                    type string;
                    description "System/Host side PRBS pattern generation enablement";
                }
                leaf prbs_gen_media_enabled {
                    type string;
                    description "Media/Line side PRBS pattern generation enablement";
                }
            }
        }

        container TRANSCEIVER_INFO {
            sonic-ext:db-name "STATE_DB";
            list TRANSCEIVER_INFO_LIST {
                key "ifname";
                config false;

                leaf ifname {
                    type leafref {
                        path "/prt:sonic-port/prt:PORT/prt:PORT_LIST/prt:name";
                    }
                }
                leaf type {
                    type string;
                    description "Identifier";
                }
                leaf type_abbrv_name {
                    type string;
                    description "Abbreviation Name";
                }
                leaf manufacturename {
                    type string;
                    description "Vendor Name";
                }
                leaf modelname {
                    type string;
                    description "Vendor Part Name";
                }
                leaf hardwarerev {
                    type string;
                    description "Vendor Revision";
                }
                leaf serialnum {
                    type string;
                    description "Vendor Serial Name";
                }
                leaf media_type {
                    type string;
                    description "Media Type";
                }
                leaf power_class {
                    type string;
                    description "Power Class";
                }
                leaf revision_compliance {
                    type string;
                    description "Revision Compliance";
                }
                leaf is_qualified {
                    type boolean;
                    description "Indicates if the component is
                         qualified to be used by the system vendor.";
                    
                }
                leaf max-module-power{
                    type decimal64 {
                        fraction-digits 2;
                    }
                    description "The maximum power the xcvr can draw (in watts)";
                  units "W";
                }
                leaf is-high-power-media {
                  description
                    "Flag to indicate if the media is a high-power optics.";
                  type boolean;
                }
                leaf media-lockdown-state {
                  description
                    "To indicate whether the media is locked";
                  type boolean;
                }
            }
        }

    }

}
