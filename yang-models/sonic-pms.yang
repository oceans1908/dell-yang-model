module sonic-pms {
    namespace "http://github.com/Azure/sonic-pms";
    prefix spms;
    yang-version 1.1;

    import sonic-extension {
        prefix sonic-ext;
    }

    import sonic-port {
        prefix prt;
    }

    import sonic-portchannel {
        prefix spc;
    }

    import ietf-yang-types {
        prefix yang;
    }

    organization
        "SONiC";

    contact
        "SONiC";

    description
        "SONiC PMS yang model";

    revision "2024-08-15" {
        description
            "Added support for sticky-mac feature.";
        reference "0.1.1";
    }

    revision 2021-05-10 {
        description
            "Initial revision.";
        reference "0.1.0";
    }

    grouping pms_port_config {
        leaf admin_enable {
            type boolean;
            sonic-ext:custom-validation ValidatePmsPort;
            description
                "Enable/Disable PMS";
        }

        leaf maximum {
            type uint16 {
                range "1..4097" {
                    error-message "Invalid value.";
                }
            }
            default 1;
            sonic-ext:custom-validation ValidatePmsPort;
            description
                "Set the maximum number of allowed MAC addresses on a port";
        }

        leaf violation {
            type string;
            sonic-ext:custom-validation ValidatePmsPort;
            description
                "PMS violation action";
        }

        leaf sticky_mac {
            type boolean;
            sonic-ext:custom-validation ValidatePmsPort;
            description
                "Enable/Disable sticky-mac feature";
        }
    }

    container sonic-pms {
        container PMS_PORT {
            list PMS_PORT_LIST {
                key "ifname";

                leaf ifname {
                    type union {
                        type leafref {
                            path "/prt:sonic-port/prt:PORT/prt:PORT_LIST/prt:name";
                        }
                        type leafref {
                            path "/spc:sonic-portchannel/spc:PORTCHANNEL/spc:PORTCHANNEL_LIST/spc:name";
                        }
                    }
                    description
                        "Reference of port on which PMS to be configured.";
                }

                uses pms_port_config;
            }
        }

        container _PMS_PORT_TABLE {
            config false;

            list _PMS_PORT_TABLE_LIST {
                sonic-ext:db-name "ASIC_DB";
                key "ifname";

                leaf ifname {
                    type leafref {
                        path "/prt:sonic-port/prt:PORT/prt:PORT_LIST/prt:name";
                    }
                    description
                        "Reference of port on which PMS is configured.";
                }
                leaf curr_address {
                    type uint16;
                    description
                        "total no of MAC address learnt on this port";
                }

                leaf violation_count {
                    type uint32;
                    description
                        "No of times violation has been hit on this port";
                }

            }
        }

        container PMS_STICKY_FDB {
          sonic-ext:db-name "EVENT_DB";
          sonic-ext:key-delim "|";
          config false;

          description "Sticky MAC address table of Port MAC security feature.";
 
          list PMS_STICKY_FDB_LIST {
            key "vlan mac_address";
            description "Sticky MAC address table entry.";

            leaf vlan {
              type string {
                pattern "Vlan(409[0-5]|40[0-8][0-9]|[1-3][0-9]{3}|[1-9][0-9]{2}|[1-9][0-9]|[1-9])" {
                  error-message "Invalid Vlan name pattern";
                  error-app-tag vlan-name-invalid;
                }
              }
              description "VLAN on which the MAC address is present.";
            }

            leaf mac_address {
              type yang:mac-address;
              sonic-ext:custom-validation ValidateFdbMacAddress;
              description
                "MAC address for the sticky MAC address table entry.";
            }

            leaf port {
              type union {
                type leafref {
                  path "/prt:sonic-port/prt:PORT/prt:PORT_LIST/prt:name";
                }
                type leafref {
                  path "/spc:sonic-portchannel/spc:PORTCHANNEL/spc:PORTCHANNEL_LIST/spc:name";
                }
              }
              description "Interface on which the MAC address is present.";
            }
          }
        }
    }
}
