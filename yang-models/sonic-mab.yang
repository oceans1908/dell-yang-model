module sonic-mab {
    namespace "http://github.com/Azure/sonic-mab";
    prefix mab;
    yang-version 1.1;

    import sonic-port {
        prefix prt;
    }

    import sonic-extension {
        prefix sonic-ext;
    }

    organization
        "SONiC";

    contact
        "SONiC";

    description
        "This module allows configuration of MAC Authentication Bypass (MAB) on an interface.";

    revision 2021-07-09 {
        description
            "Initial revision.";

    }

    typedef mab_auth_type_enumeration {
        type enumeration {
            enum pap;
            enum chap;
            enum eap-md5;
        }
    }

    container sonic-mab {

	container MAB_GLOBAL_CONFIG_TABLE {

	     description
		"Global configuration of MAC Authentication Bypass (MAB).";

	     list MAB_GLOBAL_CONFIG_TABLE_LIST {
			key "global";

		leaf global {
                   type enumeration {
                      enum GLOBAL;
                   }
                }

		leaf group_size {
		   type uint8 {
		      range "1|2|4|12" {
			 error-message "group size value must be 1 or 2 or 4 or 14.";
			 error-app-tag group-size-invalid;
		      }
                   }
                   default 2;
                }

               	leaf separator {
		   type string {
			pattern '[-]|[:]|[.]';
                    }
                    default ":";
                }

                leaf case {
                   type enumeration {
                      enum lowercase;
                      enum uppercase;
                   }
                   default uppercase;
                }
	     }
	}

	container MAB_PORT_CONFIG_TABLE {

             description
                "Configuration of MAC Authentication Bypass (MAB) on an interface.";

             list MAB_PORT_CONFIG_TABLE_LIST {
		key "port";
                sonic-ext:custom-validation ValidateMabPortChannelIntf;
                sonic-ext:custom-validation ValidateMabRoutingIntfCheck;

                leaf port {
                   type leafref {
                        path "/prt:sonic-port/prt:PORT/prt:PORT_LIST/prt:name";
                   }
                   description
                        "Name of the interface on which MAB config get applied.";
                 }

		leaf mab_enable {
                    type boolean;
                    description
                    	"MAB status Enabled / Disabled.";
                }

		leaf mab_auth_type {
                    type mab_auth_type_enumeration;
                    default eap-md5;
		}

                leaf server_timeout {
                   type uint32 {
                      range 10..65535 {
                         error-message "server timeout value must be in range of 10-65535.";
                         error-app-tag server-timeout-invalid;
                      }
                   }
                   units "seconds";
                   description
                      "The timer starts when the access device sends a RADIUS Access-Request packet
                      to the Authentication server. The MAB authentication fails, if no response
                      is received during server timeout period.";
                   }
               }
     }
   }
}
