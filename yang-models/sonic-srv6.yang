module sonic-srv6 {
    namespace "http://github.com/sonic-net/sonic-srv6";
    prefix srv6;
    yang-version 1.1;

	import ietf-inet-types {
		prefix inet;
	}

    import sonic-vrf {
		prefix vrf;
	}

    revision 2024-12-05 {
		description
			"Initial revision.";
	}

    container sonic-srv6 {

        container SRV6_MY_LOCATORS {
            list SRV6_MY_LOCATORS_LIST {
                key "locator_name";

                leaf locator_name {
                    type string;
                }

                leaf prefix {
                    type inet:ipv6-address;
                    mandatory true;
                }

                leaf block_len {
                    type uint8 {
                        range "1..128";
                    }

                    default 32;
                }

                leaf node_len {
                    type uint8 {
                        range "1..128";
                    }

                    default 16;
                }

                leaf func_len {
                    type uint8 {
                        range "0..128";
                    }

                    default 16;
                }

                leaf arg_len {
                    type uint8 {
                        range "0..128";
                    }

                    default 0;
                }

                must 'block_len + node_len + func_len + arg_len <= 128';

                leaf vrf {
                    type union {
                        type leafref {
                            path "/vrf:sonic-vrf/vrf:VRF/vrf:VRF_LIST/vrf:vrf_name";
                        }
                        type string {
                            pattern 'default';
                        }
                    }
                    description "VRF name";

                    default "default";
                }
            }
        }

        container SRV6_MY_SIDS {
            list SRV6_MY_SIDS_LIST {
                key "locator ip_prefix";

                leaf ip_prefix {
                    type inet:ipv6-prefix;
                }

                leaf locator {
                    type leafref {
                        path "/srv6:sonic-srv6/srv6:SRV6_MY_LOCATORS/srv6:SRV6_MY_LOCATORS_LIST/srv6:locator_name";
                    }
                }

                leaf action {
                    type enumeration {
                        enum uN;
                        enum uDT46;
                    }
                }

                leaf decap_vrf {
                    type union {
                        type leafref {
                            path "/vrf:sonic-vrf/vrf:VRF/vrf:VRF_LIST/vrf:vrf_name";
                        }
                        type string {
                            pattern 'default';
                        }
                    }
                    description "VRF name used for decapsulation";

                    default "default";
                }

                leaf decap_dscp_mode {
                    type enumeration {
                        enum uniform;
                        enum pipe;
                    }
                }
            }
        }

    }
}
