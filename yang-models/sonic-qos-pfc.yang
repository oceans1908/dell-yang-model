module sonic-qos-pfc {
  namespace "http://github.com/Azure/sonic-qos-pfc";
  prefix sonic-qos-pfc;

  yang-version 1.1;

  import sonic-extension {
      prefix sonic-ext;
  }

  import sonic-port {
      prefix prt;
  }

  organization
      "SONiC";

  contact
      "SONiC";

  description
      "SONIC QoS Priority-based Flow Control";

  revision 2020-07-16 {
      description
          "Initial revision.";
  }

/*
 * RPCs
*/
    rpc rpc_clear_qos_pfc {
        description "RPC for clearing interface PFC watchdog counters.";

        input {
            leaf interface-param {
                type string;
                    description
                        "parameter for clearing counters - all or interface type(Ethernet/PortChannel) or interface name";
                }
        }
        output {
            leaf status {
                type int32;
                description
                    "The status of the operation execution request.";
            }
            leaf status-detail {
                type string;
                description
                    "The detailed status of the operation execution request.";
            }
        }
    }

  container sonic-qos-pfc {

    container PFC_WD {
      sonic-ext:db-name "CONFIG_DB";
      list PFC_WD_LIST {
        key "ifname";

        leaf ifname {
            type union {
                 type leafref {
                      path "/prt:sonic-port/prt:PORT/prt:PORT_LIST/prt:name";
                 }
                 type string {
                     pattern "GLOBAL";
                 }

            }
        }

        leaf action {
          type enumeration {
            enum drop;
            enum forward;
            enum  alert;
          }
          description
            "PFC watchdog action when entering storm state.";
        }

        leaf detection_time {
          type uint32 {
            range 100..5000;
          }
          description
            "Detection interval for pause storm.";
        }

        leaf restoration_time {
          type uint32 {
            range 100..60000;
          }
          description
            "Time delay before resuming normal PFC operation.";
        }

        leaf POLL_INTERVAL {
          type uint32 {
            range 100..3000;
          }
          description
            "Priority-based Flow Control global watchdog polling
             interval.";
        }
      }
    }
  }
}
